FME workspace SendToWebSockets.fmw
Title: none2none

JMSReceiver_2
    JMS_CONNECTION_FACTORY = ConnectionFactory
    JMS_TYPE = ACTIVEMQ
    JMS_URL = tcp://54.81.254.73:61616
    JMS_DESTINATION = dynamicQueues/MeasurementsG1,dynamicQueues/MeasurementsG2,dynamicQueues/MeasurementsG3,dynamicQueues/MeasurementsG4
    -> JSONFlattener
JSONFlattener
    RECURSIVE = Yes
    NEW_ATTRIBUTES = LoaderID UploadedTime CapturedTime Latitude Longitude
    JSON_ATTR = jms_content
    -> JSONTemplater
JSONTemplater
    ROOT_QUERY_EXPR:
      {
          'ws_op': "send",
          'ws_msg': fme:get-attribute("jms_content")
      }
    VISIBLE_QUERY_VALIDATE = Yes
    RESULT_ATTRIBUTE = _result
    -> AttributeFilter
AttributeFilter
    ATTR_NAME = jms_destination
    ATTR_VALUES = <EMPTY>,<MISSING>,<NULL>,<UNFILTERED>,dynamicQueues/MeasurementsG1,dynamicQueues/MeasurementsG2,dynamicQueues/MeasurementsG3,dynamicQueues/MeasurementsG4
    dynamicQueues/MeasurementsG1 -> WebSocketSender_1
    dynamicQueues/MeasurementsG2 -> WebSocketSender_2
    dynamicQueues/MeasurementsG3 -> WebSocketSender_3
    dynamicQueues/MeasurementsG4 -> WebSocketSender_4
WebSocketSender_1
    VERIFY_SSL_CERTIFICATES = Yes
    HOST = wss://fmewt15-safe-software.fmecloud.com:7078/websocket
    PREAMBLE:
      {
          ws_op: "open",
          ws_stream_id: "group1"
      }
    DATA = @Value(_result)
WebSocketSender_2
    VERIFY_SSL_CERTIFICATES = Yes
    HOST = wss://fmewt15-safe-software.fmecloud.com:7078/websocket
    PREAMBLE:
      {
          ws_op: "open",
          ws_stream_id: "group2"
      }
    DATA = @Value(_result)
WebSocketSender_3
    VERIFY_SSL_CERTIFICATES = Yes
    HOST = wss://fmewt15-safe-software.fmecloud.com:7078/websocket
    PREAMBLE:
      {
          ws_op: "open",
          ws_stream_id: "group3"
      }
    DATA = @Value(_result)
WebSocketSender_4
    VERIFY_SSL_CERTIFICATES = Yes
    HOST = wss://fmewt15-safe-software.fmecloud.com:7078/websocket
    PREAMBLE:
      {
          ws_op: "open",
          ws_stream_id: "group4"
      }
    DATA = @Value(_result)
